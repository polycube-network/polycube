module firewall {
  yang-version 1.1;
  namespace "http://polycube.network/firewall";
  prefix "firewall";

  import polycube-base { prefix "polycube-base"; }
  import polycube-transparent-base { prefix "polycube-transparent-base"; }

  organization "Polycube open source project";
  description "YANG data model for the Polycube Firewall service";

  polycube-base:service-description "Firewall Service";
  polycube-base:service-version "2.0";
  polycube-base:service-name "firewall";
  polycube-base:service-min-kernel-version "4.14.0";

  uses "polycube-transparent-base:transparent-base-yang-module";

  typedef action {
    type enumeration {
      enum DROP;
      enum LOG;
      enum ACCEPT;
    }
    default ACCEPT;
  }

  typedef conntrackstatus {
    type enumeration {
      enum NEW;
      enum ESTABLISHED;
      enum RELATED;
      enum INVALID;
    }
  }

  typedef operation {
    type enumeration {
      enum INSERT;
      enum APPEND;
      enum DELETE;
      enum UPDATE;
    }
  }

  grouping rule-fields {
    leaf src {
      type string;
      description "Source IP Address.";
      polycube-base:init-only-config;
      polycube-base:cli-example "10.0.0.1/24";
    }

    leaf dst {
      type string;
      description "Destination IP Address.";
      polycube-base:init-only-config;
      polycube-base:cli-example "10.0.0.2/24";
    }

    leaf l4proto {
      type string;
      polycube-base:init-only-config;
      description "Level 4 Protocol.";
    }

    leaf sport {
      type uint16;
      polycube-base:init-only-config;
      description "Source L4 Port";
    }

    leaf dport {
      type uint16;
      polycube-base:init-only-config;
      description "Destination L4 Port";
    }

    leaf tcpflags {
      type string;
      polycube-base:init-only-config;
      description "TCP flags. Allowed values: SYN, FIN, ACK, RST, PSH, URG, CWR, ECE. ! means set to 0.";
      polycube-base:cli-example "!FIN,SYN,!RST,!ACK";
    }

    leaf conntrack {
      type conntrackstatus;
      polycube-base:init-only-config;
      description "Connection status (NEW, ESTABLISHED, RELATED, INVALID)";
    }

    leaf action {
      type action;
      polycube-base:init-only-config;
      description "Action if the rule matches. Default is ACCEPT.";
      polycube-base:cli-example "DROP, ACCEPT, LOG";
    }

    leaf description {
      type string;
      polycube-base:init-only-config;
      description "Description of the rule.";
      polycube-base:cli-example "This rule blocks incoming SSH connections.";
    }
  }

  leaf conntrack {
    type enumeration {
      enum ON;
      enum OFF;
    }
    description "Enables the Connection Tracking module. Mandatory if connection tracking rules are needed. Default is ON.";
  }

  leaf accept-established {
    type enumeration {
      enum ON;
      enum OFF;
    }
    description "If Connection Tracking is enabled, all packets belonging to ESTABLISHED connections will be accepted automatically. Default is ON.";
  }

  list session-table {
    key "src dst l4proto sport dport";
    config false;
    leaf src {
      type string;
      config false;
      description "Source IP";
    }

    leaf dst {
      type string;
      config false;
      description "Destination IP";
    }

    leaf l4proto {
      type string;
      config false;
      description "Level 4 Protocol.";
    }


    leaf sport {
      type uint16;
      description "Source Port";
      config false;
    }

    leaf dport {
      type uint16;
      description "Destination";
      config false;
    }

    leaf state {
      type string;
      config false;
      description "Connection state.";
    }

    leaf eta {
      type uint32;
      config false;
      description "Last packet matching the connection";
    }
  }

  list chain {
    key "name";

    leaf name {
      type enumeration {
        enum INGRESS;
        enum EGRESS;
        enum INVALID;
      }
      description "Chain in which the rule will be inserted. Default: INGRESS.";
      polycube-base:cli-example "INGRESS, EGRESS.";
    }

    leaf default {
      type action;
      description "Default action if no rule matches in the ingress chain. Default is ACCEPT.";
      polycube-base:cli-example "DROP, ACCEPT, LOG";
    }

    list stats {
      key "id";
      config false;
      leaf id {
        type uint32;
        config false;
        description "Rule Identifier";
      }

      leaf pkts {
        type uint64;
        description "Number of packets matching the rule";
        config false;
      }

      leaf bytes {
        type uint64;
        description "Number of bytes matching the rule";
        config false;
      }

      uses "firewall:rule-fields";
    }

    list rule {
      key "id";
      leaf id {
        type uint32;
        description "Rule Identifier";
      }

      uses "firewall:rule-fields";
    }

    action append {
      input {
        uses "firewall:rule-fields";
      }
      output {
        leaf id {
          type uint32;
        }
      }
    }

    action insert {
      input {
        leaf id {
          type uint32;
        }
        uses "firewall:rule-fields";
      }
      output {
        leaf id {
          type uint32;
        }
      }
    }

    action delete {
      input {
        uses "firewall:rule-fields";
      }
    }

    action batch {
      input {
        list rules {
          key "id";
          leaf id {
            type uint32;
          }
          leaf operation {
            type operation;
          }
          uses "firewall:rule-fields";
        }
      }
    }

    action reset-counters {
      description "Reset the counters to 0 for the chain.";
      output {
        leaf result {
          type boolean;
          description "True if the operation is successful";
        }
      }
    }
  }
}
