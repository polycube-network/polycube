module simpleforwarder {
  yang-version 1.1;
  namespace "http://polycube.network/simpleforwarder";
  prefix "simpleforwarder";

  import polycube-base { prefix "polycube-base"; }
  import polycube-standard-base { prefix "polycube-standard-base"; }

  organization "Polycube open source project";
  description "YANG data model for the Polycube Simple Forwarder service";

  polycube-base:service-description "Simple Forwarder Base Service";
  polycube-base:service-version "2.0";
  polycube-base:service-name "simpleforwarder";
  polycube-base:service-min-kernel-version "4.14.0";

  uses "polycube-standard-base:standard-base-yang-module";

  list actions {
    key "inport";
    description "Entry of the Actions table";
    polycube-base:name-metric "simpleforwarder_actions_entries";
    polycube-base:type-metric "GAUGE";
    polycube-base:path-metric '$.actions.length';
    polycube-base:help-metric "Number of entries of the Actions table";
    leaf inport {
      type string;
      mandatory true;
      description "Ingress port";
    }

    leaf action {
      type enumeration {
        enum DROP;
        enum SLOWPATH;
        enum FORWARD;
      }
      mandatory true;
      description "Action associated to the current table entry (i.e., DROP, SLOWPATH, or FORWARD; default: DROP)";
    }

    leaf outport {
      type string;
      description "Output port (used only when action is FORWARD)";
    }
  }
}
