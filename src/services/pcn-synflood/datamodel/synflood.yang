module synflood {
  yang-version 1.1;
  namespace "http://polycube.network/synflood";
  prefix "synflood";

  import polycube-base { prefix "polycube-base"; }
  import polycube-transparent-base { prefix "polycube-transparent-base"; }

  organization "Polycube open source project";
  description "YANG data model for the Network Monitor";

  polycube-base:service-description "TCP SYN Flood Monitor Service";
  polycube-base:service-version "2.0";
  polycube-base:service-name "synflood";
  polycube-base:service-min-kernel-version "4.11.0";

  uses "polycube-transparent-base:transparent-base-yang-module";

  container stats {
    description "Statistics for SYN Flood Monitor";
    config false;

    leaf tcpattemptfails {
        type string;
        description "Number of failed TCP connections";
        config false;
    }

    leaf tcpoutrsts {
        type string;
        description "Number of TCP segments sent, containing the RST flag";
        config false;
    }

    leaf deliverratio {
        type string;
        description "Ratio between the number of IP pkts delivered to application protocols and the total number of received pkts";
        config false;
    }

    leaf responseratio {
        type string;
        description "Ratio between the number of IP pkts requests to send by application protocols and the total number of received pkts";
        config false;
    }

    leaf lastupdate {
        type uint64;
        description "last update (time from epoch in milliseconds)";
        config false;
    }
  }
}
