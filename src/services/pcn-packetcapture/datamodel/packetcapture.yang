module packetcapture {
  yang-version 1.1;
  namespace "http://polycube.network/packetcapture";
  prefix "packetcapture";
 
  import polycube-base { prefix "polycube-base"; }
  import ietf-inet-types { prefix "inet"; }
  import ietf-yang-types { prefix "yang";  }
  import polycube-transparent-base { prefix "polycube-transparent-base"; }
 
  organization "Polycube open source project";
  description "YANG data model for the Polycube Transparent-Packetcapture service";
 
  polycube-base:service-description "Transparent-Packetcapture Service";
  polycube-base:service-version "2.0";
  polycube-base:service-name "packetcapture";
  polycube-base:service-min-kernel-version "4.14.0";
 
  uses "polycube-transparent-base:transparent-base-yang-module";
 
 
  leaf capture {
    type enumeration {
      enum INGRESS;
      enum EGRESS;
      enum BIDIRECTIONAL;
      enum OFF;
    }
    default OFF;
    description "Packet capture status";
  }
  
  leaf anonimize {
     type boolean;
     default false;
  }
 
  leaf dump {
    type string;
    description "dump capture";
  }
 
  leaf networkmode {
    type boolean;
    default false;
    description "Operating mode";
  }

  leaf snaplen {
    type uint32;
    default 262144;
    description "Snapshot length";
  }

  leaf filter {
    type string;
    description "filtering string (e.g., 'host 1.2.3.4 and src port 80')";
  }

  container globalheader {
    description "global header info";

    leaf magic {
     type uint32;
     description "magic number";
    }
 
    leaf version_major {
     type uint16;
     description "major version number";
    }
 
    leaf version_minor {
     type uint16;
     description "minor version number";
    }
 
    leaf thiszone {
     type int32;
     description "GMT to local correction";
    }

    leaf sigfigs {
     type uint32;
     description "accuracy of timestamps";
    }

    leaf snaplen {
     type uint32;
     description "max length of captured packets, in octets";
    }

    leaf linktype {
     type uint32;
     description "Capture linktype (eg. ethernet, wifi..)";
    }
  }

  container packet {
    description "packet info";

    leaf capturelen {
     type uint32;
     description "Capture length";
    }
 
    leaf packetlen {
     type uint32;
     description "Packet length";
    }
 
    leaf timestamp-seconds {
     type uint32;
     units seconds;
     description "timestamp - seconds";
    }
 
    leaf timestamp-microseconds {
     type uint32;
     description "timestamp - microseconds";
    }

    leaf rawdata {
     type string;
     description "packet raw data";
    }
  }
}
