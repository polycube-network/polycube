module k8sfilter {
  yang-version 1.1;
  namespace "http://polycube.network/nat";
  prefix "k8sfilter";

  import polycube-base { prefix "polycube-base"; }
  import polycube-standard-base { prefix "polycube-standard-base"; }

  organization "Polycube open source project";
  description "YANG data model for the Polycube traffic filter for Kubernetes";

  polycube-base:service-description "Kubernetes Traffic Filtering Service";
  polycube-base:service-version "2.0";
  polycube-base:service-name "k8sfilter";
  polycube-base:service-min-kernel-version "4.14.0";

  uses "polycube-standard-base:standard-base-yang-module" {
    augment ports {
      leaf type {
        type enumeration {
          enum EXTERNAL { description "Connected to NIC"; }
          enum INTERNAL { description "Connected to LBRP"; }
        }
        mandatory true;
        config true;
        polycube-base:init-only-config;
        description "...";
      }
    }
  }

  leaf nodeport-range {
    type string;
    description "Port range used for NodePort services";
    default "30000-32767";
    polycube-base:cli-example "30000-32767";
  }
}
