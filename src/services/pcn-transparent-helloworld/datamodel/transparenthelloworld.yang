module transparenthelloworld {
  yang-version 1.1;
  namespace "http://polycube.network/trhelloworld";
  prefix "trhelloworld";

  import polycube-base { prefix "polycube-base"; }
  import polycube-transparent-base { prefix "polycube-transparent-base"; }

  organization "Polycube open source project";
  description "YANG data model for the Polycube Transparent Helloworld service";

  polycube-base:service-description "Transparent Helloworld Service";
  polycube-base:service-version "1.0";
  polycube-base:service-name "trhelloworld";
  polycube-base:service-min-kernel-version "4.14.0";

  uses "polycube-transparent-base:transparent-base-yang-module";

  leaf ingress-action {
    type enumeration {
      enum DROP;
      enum PASS;
      enum SLOWPATH;
    }
    default PASS;
    description "Action performed on ingress packets";
    polycube-base:cli-example "DROP/PASS/SLOWPATH (default: PASS)";
  }

  leaf egress-action {
    type enumeration {
      enum DROP;
      enum PASS;
      enum SLOWPATH;
    }
    default PASS;
    description "Action performed on egress packets";
    polycube-base:cli-example "DROP/PASS/SLOWPATH (default: PASS)";
  }
}
